FME workspace CARGA_CONDUTORES.fmw

Parameters:
- SourceDataset_XLSXR = $(FME_MF_DIR)espec_condutores.xlsx   # Source Microsoft Excel File(s)
- SourceDataset_XLSXR_5 = $(FME_MF_DIR)modulo_componente_condutores.xlsx   # Source Microsoft Excel File(s)

Readers:
- XLSXR_3: XLSXR from $(SourceDataset_XLSXR)
- XLSXR_1: XLSXR from $(SourceDataset_XLSXR_5)

Writers:
- ORACLE_NONSPATIAL_1: ORACLE_NONSPATIAL to Modulo Construtivo - Homol

Dados (reader XLSXR_3)
    attributes: DS_MODULO char(45), CD_CABO_DISTR char(29), ID_QTD_FASE number(2,0)
    -> DuplicateFilter_2
DuplicateFilter_2
    INPUT_ORDERED_CHOICE = No
    KEYATTR = CD_CABO_DISTR ID_QTD_FASE DS_MODULO
    UNIQUE -> FeatureHolder
FeatureHolder
    -> Aggregator
    -> ESPEC_MOD [LEFT]
Aggregator
    ACCUM_ATTRS_NAME = Drop Incoming Attributes
    GROUP_BY = DS_MODULO
    MODE = Attributes Only
    ORDERED = No
    SEP = ,
    AGGREGATE -> AttributeCreator
AttributeCreator
    ATTR_TABLE = SET_TO ID_GRUPO_MODULO = -10
    -> SQLExecutor [INITIATOR]
SQLExecutor
    COMBINE_ATTRS = Keep Initiator Attributes if Conflict
    COMBINE_GEOM = Initiator Geometry Only
    DATASET = Modulo Construtivo - Homol
    EXPOSED_ATTRIBUTE_LIST = ID_MODULO
    FORMAT = ORACLE_NONSPATIAL
    ORACLE_NONSPATIAL_NAMED_CONNECTION = Modulo Construtivo - Homol
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    SQL_STATEMENT = SELECT SEQ_ID_MODULO.NEXTVAL as ID_MODULO FROM DUAL
    RESULT -> Sampler
    RESULT -> FeatureHolder_4
Sampler
    GROUP_BY = fme_feature_type
    RATE = 1
    SAMPLE_MODE = No
    SAMPLE_TYPE_LONG = First N Features
    SAMPLED -> DEL_COMPONENTE_MODULO
    SAMPLED -> DEL_ESPEC_MOD_ISOLADOR_AT
    SAMPLED -> DEL_MODULO
DEL_COMPONENTE_MODULO: DatabaseDeleter
    CONDITION = WHERE Clause
    DATASET = Modulo Construtivo - Homol
    FORMAT = ORACLE_NONSPATIAL
    ORACLE_NONSPATIAL_NAMED_CONNECTION = Modulo Construtivo - Homol
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    TABLE = MODULO_CONSTRUTIVO.COMPONENTE_MODULO
    WHERE_CLAUSE = ID_MODULO in (SELECT ID_MODULO FROM modulo WHERE ID_GRUPO_MODULO = @Value(ID_GRUPO_MODULO))
DEL_ESPEC_MOD_ISOLADOR_AT: DatabaseDeleter
    CONDITION = WHERE Clause
    DATASET = Modulo Construtivo - Homol
    FORMAT = ORACLE_NONSPATIAL
    ORACLE_NONSPATIAL_NAMED_CONNECTION = Modulo Construtivo - Homol
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    TABLE = MODULO_CONSTRUTIVO.ESPEC_MOD_CONDUTOR
    WHERE_CLAUSE = ID_MODULO in (SELECT ID_MODULO FROM modulo WHERE ID_GRUPO_MODULO = @Value(ID_GRUPO_MODULO))
DEL_MODULO: DatabaseDeleter
    CONDITION = WHERE Clause
    DATASET = Modulo Construtivo - Homol
    FORMAT = ORACLE_NONSPATIAL
    ORACLE_NONSPATIAL_NAMED_CONNECTION = Modulo Construtivo - Homol
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    TABLE = MODULO
    WHERE_CLAUSE = ID_GRUPO_MODULO = @Value(ID_GRUPO_MODULO)
FeatureHolder_4
    -> MODULO (writer ORACLE_NONSPATIAL_1)
    -> FeatureHolder_3
MODULO (writer ORACLE_NONSPATIAL_1)
    attributes: ID_GRUPO_MODULO number, DS_MODULO varchar2(120), ID_MODULO number
FeatureHolder_3
    -> Componente_Modulo [COMP_MODULO_Right]
    -> ESPEC_MOD [RIGHT]
ESPEC_MOD: FeatureJoiner
    ATTR_CONFLICT_RES = Use Left
    GEOMETRY_HANDLING = Use Left
    JOIN_KEYS = DS_MODULO DS_MODULO AUTO
    JOIN_MODE = Inner
    JOINED -> SQLExecutor_2 [INITIATOR]
SQLExecutor_2
    COMBINE_ATTRS = Keep Initiator Attributes if Conflict
    COMBINE_GEOM = Initiator Geometry Only
    DATASET = Modulo Construtivo - Homol
    EXPOSED_ATTRIBUTE_LIST = ID_ESPEC_MODULO
    FORMAT = ORACLE_NONSPATIAL
    ORACLE_NONSPATIAL_NAMED_CONNECTION = Modulo Construtivo - Homol
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    SQL_STATEMENT = SELECT SEQ_ID_ESPEC_MODULO.NEXTVAL as ID_ESPEC_MODULO FROM DUAL
    RESULT -> ESPEC_MOD_CONDUTOR (writer ORACLE_NONSPATIAL_1)
ESPEC_MOD_CONDUTOR (writer ORACLE_NONSPATIAL_1)
    attributes: ID_ESPEC_MODULO number, ID_MODULO number, ID_QTD_FASE number, CD_CABO_DISTR varchar2(40)
Dados (reader XLSXR_1)
    attributes: DS_MODULO char(45), CD_MATERIAL number(6,0), CD_SERVICO number(7,0), QT_COMPONENTE_MODULO number(6,4), ID_OPERACAO number(2,0)
    -> DuplicateFilter
DuplicateFilter
    INPUT_ORDERED_CHOICE = No
    KEYATTR = CD_SERVICO CD_MATERIAL ID_OPERACAO DS_MODULO
    UNIQUE -> FeatureHolder_2
FeatureHolder_2
    -> Componente_Modulo [COMP_MODULO_Left]
Componente_Modulo
    CD_MATERIAL = @Value(CD_MATERIAL)
    CD_SERVICO = @Value(CD_SERVICO)
    DS_MODULO = @Value(DS_MODULO)
    StringPadder_Output -> COMPONENTE_MODULO (writer ORACLE_NONSPATIAL_1)
COMPONENTE_MODULO (writer ORACLE_NONSPATIAL_1)
    attributes: CD_MATERIAL varchar2(18), CD_SERVICO varchar2(18), QT_COMPONENTE_MODULO number(9,4), ID_OPERACAO number, ID_GRUPO_MODULO number, ID_MODULO number, ID_COMPONENTE_MODULO number

FME custom transformer Componente_Modulo

Parameters:
- DS_MODULO = @Value(DS_MODULO)   # Ds Modulo
- CD_MATERIAL = @Value(CD_MATERIAL)   # Cd Material
- CD_SERVICO = @Value(CD_SERVICO)   # Cd Servico

COMP_MODULO_Left (input)
    -> COMP_MODULO [LEFT]
COMP_MODULO_Right (input)
    -> COMP_MODULO [RIGHT]
COMP_MODULO: FeatureJoiner
    ATTR_CONFLICT_RES = Use Left
    GEOMETRY_HANDLING = Use Left
    JOIN_KEYS = DS_MODULO DS_MODULO AUTO
    JOIN_MODE = Inner
    JOINED -> SQLExecutor_3 [INITIATOR]
SQLExecutor_3
    COMBINE_ATTRS = Keep Initiator Attributes if Conflict
    COMBINE_GEOM = Initiator Geometry Only
    DATASET = Modulo Construtivo - Homol
    EXPOSED_ATTRIBUTE_LIST = ID_COMPONENTE_MODULO
    FORMAT = ORACLE_NONSPATIAL
    ORACLE_NONSPATIAL_NAMED_CONNECTION = Modulo Construtivo - Homol
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    SQL_STATEMENT = SELECT SEQ_ID_COMPONENTE_MODULO.NEXTVAL as ID_COMPONENTE_MODULO FROM DUAL
    RESULT -> StringPadder
StringPadder
    BLANK_ATTRIBUTE = No
    PADCHAR = 0
    SIDE = Left
    SRC_ATTRS = CD_SERVICO CD_MATERIAL
    WIDTH = 18
    -> StringPadder_Output (output)
StringPadder_Output (output)
